(defun c:DumpData ()
  (setq fn "g:\\My Drive\\1.Work\\ATGT\\Tool ATGT\\dwg_layers_blocks.txt")
  (setq f (open fn "w"))
  (write-line "=== LAYERS ===" f)
  (setq item (tblnext "layer" t))
  (while item
    (write-line (cdr (assoc 2 item)) f)
    (setq item (tblnext "layer"))
  )
  (write-line "=== BLOCKS DEFINED ===" f)
  (setq item (tblnext "block" t))
  (while item
    (write-line (cdr (assoc 2 item)) f)
    (setq item (tblnext "block"))
  )
  (write-line "=== INSERT ENTITIES IN DRAWING ===" f)
  (setq ss (ssget "X" '((0 . "INSERT"))))
  (if ss
    (progn
      (setq i 0)
      (while (< i (sslength ss))
        (setq ent (entget (ssname ss i)))
        (setq bname (cdr (assoc 2 ent)))
        (setq pt (cdr (assoc 10 ent)))
        (setq rot (cdr (assoc 50 ent)))
        (setq lay (cdr (assoc 8 ent)))
        (write-line (strcat bname "\t" lay "\t" (rtos (car pt) 2 4) "\t" (rtos (cadr pt) 2 4) "\t" (rtos (caddr pt) 2 4) "\t" (rtos rot 2 4)) f)
        (setq i (1+ i))
      )
    )
  )
  (close f)
  (command "_.QUIT" "_Y")
)
(c:DumpData)
