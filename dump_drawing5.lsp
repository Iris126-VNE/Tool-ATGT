(vl-load-com)
(setq fn "H:/My Drive/1.Work/ATGT/Tool ATGT/drawing5_dump.txt")
(setq f (open fn "w"))
(setq ss (ssget "X"))
(if ss
  (progn
    (setq i 0)
    (while (< i (sslength ss))
      (setq ent (ssname ss i))
      (setq elist (entget ent))
      (setq typ (cdr (assoc 0 elist)))
      (setq lay (cdr (assoc 8 elist)))
      (write-line (strcat typ "\t" lay) f)
      (setq i (1+ i))
    )
  )
)
(close f)
(command "_.QUIT" "_Y")
