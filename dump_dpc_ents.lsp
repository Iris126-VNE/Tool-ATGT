(defun c:DumpEnts ( / fn f ss i ent elist typ)
  (setq fn "G:/My Drive/1.Work/ATGT/Tool ATGT/dpc_dwg_ents.txt")
  (setq f (open fn "w"))
  (setq ss (ssget "X"))
  (if ss
    (progn
      (setq i 0)
      (while (< i (sslength ss))
        (setq ent (ssname ss i))
        (setq elist (entget ent))
        (setq typ (cdr (assoc 0 elist)))
        (write-line (strcat typ " | layer=" (cdr (assoc 8 elist))) f)
        (setq i (1+ i))
      )
    )
  )
  (close f)
  (command "_.QUIT" "_Y")
)
(c:DumpEnts)
