(defun c:DumpPoly ( / ent v elist pt f)
  (setq ent (ssname (ssget "X" '((0 . "POLYLINE"))) 0))
  (setq f (open "H:/My Drive/1.Work/ATGT/Tool ATGT/poly_coords.txt" "w"))
  (setq v (entnext ent))
  (while (and v (/= (cdr (assoc 0 (entget v))) "SEQEND"))
    (setq elist (entget v))
    (setq pt (cdr (assoc 10 elist)))
    (write-line (strcat (rtos (car pt) 2 4) "\t" (rtos (cadr pt) 2 4) "\t" (rtos (caddr pt) 2 4)) f)
    (setq v (entnext v))
  )
  (close f)
  (command "_.QUIT" "_Y")
)
(c:DumpPoly)
