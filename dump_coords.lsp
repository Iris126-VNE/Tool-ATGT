(vl-load-com)
(setq ent (ssname (ssget "X" '((0 . "POLYLINE"))) 0))
(setq obj (vlax-ename->vla-object ent))
(setq coords (vlax-safearray->list (vlax-variant-value (vla-get-coordinates obj))))
(setq f (open "H:/My Drive/1.Work/ATGT/Tool ATGT/poly_coords.txt" "w"))
(setq i 0)
(while (< i (length coords))
  (write-line (strcat (rtos (nth i coords) 2 4) "\t" (rtos (nth (+ i 1) coords) 2 4) "\t" (rtos (nth (+ i 2) coords) 2 4)) f)
  (setq i (+ i 3))
)
(close f)
(command "_.QUIT" "_Y")
